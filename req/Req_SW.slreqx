# Req_SW

## Requierments_Klimaanlage!RequiermentsKlimaAnlage: References to Requierments_Klimaanlage.xlsx (RequiermentsKlimaAnlage) (Container)
Read-only references to Microsoft Excel document.

### 1: Die Klimaanlagensteuerung muss die Temperatur auf eine voreingestellte Zieltemperatur zwischen 16°C und 28°C regeln können. (Functional)

### 2: Die Software muss die Klimaanlage so steuern, dass sie die Innenraumtemperatur in maximal 5 Minuten um mindestens 10°C herunterkühlt oder aufheizen kann. (Functional)

### 3: Die Software muss die Innenraumtemperatur auf ±1°C der eingestellten Zieltemperatur halten. (Functional)

### 4: Die Klimaanlage muss basierend auf der Innenraum- und Außentemperatur selbständig die Innenraumtemperatur auf den vom Nutzer eingestellten Sollwert regeln. (Functional)

### 5: Die Software muss eine Fehlererkennungsfunktion implementieren, die bei einem Außentemperaturen ab -20°C und niedriger, sowie +50°C und höher einen Sicherheitsmodus aktiviert. (Functional)

### 6: Die Software muss eine Fehlererkennungsfunktion implementieren, die bei einem Energieverbrauch größer als 5kW einen Sicherheitsmodus aktiviert. (Functional)

### 7: Im Sicherheitsmodus muss die Klimaanlage deaktiviert werden bis der Energieverbrauch wieder unter 5kW und die Temperatur wieder über -20°C oder unter 50°C beträgt. (Functional)

### 8: Die Regelung der Innentemperatur muss mit einem on-off button gestoppt und gestartet werden können (Functional)

### 9: Es muss eine Nutzerausgabe geben, die die derzeitige Eingestellte Temperatur anzeigt (Functional)
